-- etherhub.my - 802.3 Repeater MIB

SNMP-REPEATER-MIB DEFINITIONS ::= BEGIN

IMPORTS
    experimental, Counter, TimeTicks    FROM RFC1155-SMI
    DisplayString                       FROM RFC1213-MIB
    OBJECT-TYPE                         FROM RFC-1212;

-- All representations of MAC addresses in this MIB Module use,
-- as a textual convention (i.e. this convention does not affect
-- their encoding), the data type:

MacAddress ::= OCTET STRING (SIZE (6))    -- a 6 octet address in
                                        -- the "canonical" order
-- defined by IEEE 802.1a, i.e., as if it were transmitted least
-- significant bit first.
--
-- 16-bit addresses, if needed, are represented by setting their
-- upper 4 octets to all 0's, i.e., AAFF would be represented
-- as 00000000AAFF.

snmpDot3RptrMgt OBJECT IDENTIFIER ::= { experimental 29 }

-- groups in the SNMP Repeater Mib

rptrBasicGroup
    OBJECT IDENTIFIER ::= { snmpDot3RptrMgt 1 }

rptrMonitorGroup
    OBJECT IDENTIFIER ::= { snmpDot3RptrMgt 2 }

rptrAddrTrackGroup
    OBJECT IDENTIFIER ::= { snmpDot3RptrMgt 3 }

-- The Basic Group

-- Implementation of the Basic Group is mandatory for all
-- managed repeaters.

--
-- The Basic Repeater Table
--

rptrBasicTable OBJECT-TYPE
    SYNTAX    SEQUENCE OF RptrBasicEntry
    ACCESS    not-accessible
    STATUS    mandatory
    DESCRIPTION
            "Status information and control variables for a
            collection of repeaters in a particular system."
    ::= { rptrBasicGroup 1 }

rptrBasicEntry OBJECT-TYPE
    SYNTAX    RptrBasicEntry
    ACCESS    not-accessible
    STATUS    mandatory
    DESCRIPTION
            "Status information and control variables for a
            particular repeater in the system."
    INDEX    { rptrBasID }
    ::= { rptrBasicTable 1 }

RptrBasicEntry ::=
    SEQUENCE {
        rptrBasID
            INTEGER,
        rptrBasManufacturer
            OCTET STRING,
        rptrBasProduct
            OCTET STRING,
        rptrBasVersion
            OCTET STRING,
        rptrBasGroupCapacity
            INTEGER,
        rptrBasGroupMap
            OCTET STRING,
        rptrBasHealthState
            INTEGER,
        rptrBasHealthText

            DisplayString,
        rptrBasHealthData
            OCTET STRING,
        rptrBasReset
            INTEGER,
        rptrBasSelfTest1
            INTEGER,
        rptrBasSelfTest2
            INTEGER
    }

rptrBasID OBJECT-TYPE
    SYNTAX    INTEGER (1..1024)
    ACCESS    read-only
    STATUS    mandatory
    DESCRIPTION
            "The value of rptrID is assigned so as to uniquely
            identify a repeater in a system where a single
            agent manages multiple repeaters."
    REFERENCE
            "Reference [12] 19.2.3.2, hubID."
    ::= { rptrBasicEntry 1 }

rptrBasManufacturer OBJECT-TYPE
    SYNTAX    OCTET STRING (SIZE(3))
    ACCESS    read-only
    STATUS    mandatory
    DESCRIPTION
            "A 24-bit value that identifies the manufacturer."
    REFERENCE
            "Reference IEEE 802.1F/D7, May 1, 1991, Section
            8.2, ResourceInfo.manufacturerID."
    ::= { rptrBasicEntry 2 }

rptrBasProduct OBJECT-TYPE
    SYNTAX    OCTET STRING
    ACCESS    read-only
    STATUS    mandatory
    DESCRIPTION
            "Manufacturer-defined product identifier.  Its
            format and size are unrestricted."
    REFERENCE
            "Reference IEEE 802.1F/D7, May 1, 1991, Section
            8.2, ResourceInfo.manufacturerProductID."
    ::= { rptrBasicEntry 3 }

rptrBasVersion OBJECT-TYPE
    SYNTAX    OCTET STRING
    ACCESS    read-only
    STATUS    mandatory
    DESCRIPTION
            "Manufacturer-defined product revision
            designation.  Its format and size are
            unrestricted."
    REFERENCE
            "Reference IEEE 802.1F/D7, May 1, 1991, Section
            8.2, ResourceInfo.ManufacturerProductVersion."
    ::= { rptrBasicEntry 4 }

rptrBasGroupCapacity OBJECT-TYPE
    SYNTAX    INTEGER (1..1024)
    ACCESS    read-only
    STATUS    mandatory
    DESCRIPTION
            "The rptrBasGroupCapacity is the number of groups
            that can be contained within the repeater. Within
            each managed repeater, the groups are uniquely
            numbered in the range from 1 to
            rptrBasGroupCapacity.

            Some groups may not be present in a given repeater
            instance, in which case the actual number of
            groups present will be less than
            rptrBasGroupCapacity. The number of groups present
            will never be greater than rptrBasGroupCapacity.

            Note:  In practice, this will generally be the
            number of field-replaceable units (i.e., modules,
            cards, or boards) that can fit in the physical
            repeater enclosure, and the group numbers  will
            correspond to numbers marked on the physical
            enclosure."
    REFERENCE
            "Reference [12] 19.2.3.2, hubGroupCapacity."
    ::= { rptrBasicEntry 5 }

rptrBasGroupMap OBJECT-TYPE
    SYNTAX    OCTET STRING (SIZE(1..128))    -- bit map
    ACCESS    read-only
    STATUS    mandatory
    DESCRIPTION

            "This octet string represents the current
            configuration of groups, encoded as a bit string.
            Each group is represented by a single bit. When
            the value of a bit=1, it indicates that the group
            represented by that bit is present in the
            repeater; when zero, the group is not present.

            Note:  The bitstring mapping text below does not
            match the IETF conventions, and will be modified
            appropriately.

            The number of octets in the string is
            rptrBasGroupCapacity divided by 8, rounded up to
            the next whole number of octets.  For example, if
            rptrBasGroupCapacity is 12, the octet string
            returned by the agent will be of length two.

            The first octet will encode the configuration of
            groups 1-8, where group one is represented by the
            least significant bit of the octet.  The second
            octet will likewise encode groups 9-16.  In
            general, octet i encodes groups (8i-7) through
            (8i), where (8i-7) is represented by the least
            significant bit and (8i) by the most significant
            bit of the octet."
    REFERENCE
            "Reference [12] 19.2.3.2, hubGroupMap."
    ::= { rptrBasicEntry 6 }

rptrBasHealthState OBJECT-TYPE
    SYNTAX  INTEGER {
                other(1),            -- undefined or unknown state
                ok(2),               -- no known failures
                rptrFailure(3),      -- repeater-related failure
                groupFailure(4),     -- group-related failure
                portFailure(5),      -- port-related failure
                generalFailure(6)    -- failure, unspecified type
            }
    ACCESS    read-only
    STATUS    mandatory
    DESCRIPTION
            "The health state object indicates the operational
            state of the repeater. The rptrBasHealthData and
            rptrBasHealthText objects may be consulted for
            more specific information about the state of the

            repeater's health.

            In the case of multiple kinds of failures (e.g.,
            repeater failure and port failure), the value of
            this attribute shall reflect the highest priority
            failure in the following order:
                rptrFailure(3)
                groupFailure(4)
                portFailure(5)
                generalFailure(6)"
    REFERENCE
            "Reference [12] 19.2.3.2, hubHealthState."
    ::= { rptrBasicEntry 7 }

rptrBasHealthText OBJECT-TYPE
    SYNTAX    DisplayString (SIZE (0..255))
    ACCESS    read-only
    STATUS    mandatory
    DESCRIPTION
            "The health text object is a text string that
            provides information relevant to the operational
            state of the repeater. Agents may use this
            mechanism to provide detailed failure information
            or instructions for problem resolution. The
            contents are agent-specific."
    REFERENCE
            "Reference [12] 19.2.3.2, hubHealthText."
    ::= { rptrBasicEntry 8 }

rptrBasHealthData OBJECT-TYPE
    SYNTAX    OCTET STRING (SIZE (0..255))
    ACCESS    read-only
    STATUS    mandatory
    DESCRIPTION
            "The health data object is a block of data octets
            that provides information relevant to the
            operational state of the repeater. The encoding of
            this data block is agent-dependent. Agents may use
            this mechanism to provide detailed failure
            information or instructions for problem
            resolution."
    REFERENCE
            "Reference [12] 19.2.3.2, hubHealthData."
    ::= { rptrBasicEntry 9 }

rptrBasReset OBJECT-TYPE
    SYNTAX    INTEGER {
                noReset(1),
                reset(2)
            }
    ACCESS    read-write
    STATUS    mandatory
    DESCRIPTION
            "Setting this variable to reset(2) causes a
            transition to the START state of Fig 9-2 in
            section 9 [11].

            Setting this variable to noReset(1) has no effect.
            The agent will always return the value noReset(1)
            when this variable is read.

            This action does not reset the management counters
            defined in this document nor does it affect the
            portAdminState parameters. Included in this action
            is the execution of rptrBasSelfTest2. As a result
            of this action a rptrReset trap will be sent.

            Note:  This action may result in the loss of
            packets."
    REFERENCE
            "Reference [12] 19.2.3.3, resetHubAction."
    ::= { rptrBasicEntry 10 }

rptrBasSelfTest1 OBJECT-TYPE
    SYNTAX    INTEGER {
                noSelfTest(1),
                selfTest(2)
            }
    ACCESS    read-write
    STATUS    mandatory
    DESCRIPTION
            "Setting this variable to selfTest(2) causes the
            repeater to perform a agent-specific, non-
            disruptive self-test that has the following
            characteristics: (1)  The nature of the tests is
            not specified. (2)  The test does not change the
            state of the repeater or management information
            about the repeater. (3)  The test does not inject
            packets onto any segment. (4)  The test does not
            prevent the relay of any packets. (5)  The test

            does not interfere with management functions.

            After performing this test the agent will update
            the repeater health information. If a change in
            the repeater health has occurred, the agent will
            send a rptrHealth trap.

            Setting this variable to noSelfTest(1) has no
            effect. The agent will always return the value
            noSelfTest(1) when this variable is read."
    REFERENCE
            "Reference [12] 19.2.3.3, executeSelfTest1Action."
    ::= { rptrBasicEntry 11 }

rptrBasSelfTest2 OBJECT-TYPE
    SYNTAX    INTEGER {
                noSelfTest(1),
                selfTest(2)
            }
    ACCESS    read-write
    STATUS    mandatory
    DESCRIPTION
            "Setting this variable to selfTest(2) causes the
            repeater to perform a agent-specific, disruptive
            self-test that has the following characteristics:
            (1)  The nature of the tests is not specified. (2)
            The test resets the repeater but without affecting
            management information about the repeater. (3)
            The test does not inject packets onto any segment.
            (4)  Packets received during the test may or may
            not be relayed.

            After performing this test the agent will update
            the repeater health information. If a change in
            the repeater health has occurred, the agent will
            send a rptrHealth trap.

            Setting this variable to noSelfTest(1) has no
            effect.  The agent will always return the value
            noSelfTest(1) when this variable is read."
    REFERENCE
            "Reference [12] 19.2.3.3, executeSelfTest2Action."
    ::= { rptrBasicEntry 12 }

--

-- The Basic Port Group Table
--

rptrBasicGroupTable OBJECT-TYPE
    SYNTAX    SEQUENCE OF RptrBasicGroupEntry
    ACCESS    not-accessible
    STATUS    mandatory
    DESCRIPTION
            "Table of descriptive and status information about
            the groups of ports."
    ::= { rptrBasicGroup 2 }

rptrBasicGroupEntry OBJECT-TYPE
    SYNTAX    RptrBasicGroupEntry
    ACCESS    not-accessible
    STATUS    mandatory
    DESCRIPTION
            "An entry in the table, containing information
            about a single group of ports."
    INDEX    { rptrBasGroupRptrID, rptrBasGroupID }
    ::= { rptrBasicGroupTable 1 }

RptrBasicGroupEntry ::=
    SEQUENCE {
        rptrBasGroupRptrID
            INTEGER,
        rptrBasGroupID
            INTEGER,
        rptrBasGroupDescr
            DisplayString,
        rptrBasGroupObjectID
            OBJECT IDENTIFIER,
        rptrBasGroupUpTime
            TimeTicks,
        rptrBasGroupNumOfPorts
            INTEGER
    }

rptrBasGroupRptrID OBJECT-TYPE
    SYNTAX    INTEGER (1..1024)
    ACCESS    read-only
    STATUS    mandatory
    DESCRIPTION
            "This variable identifies the repeater containing
            the group for which this entry contains

            information."
    ::= { rptrBasicGroupEntry 1 }

rptrBasGroupID OBJECT-TYPE
    SYNTAX    INTEGER (1..1024)
    ACCESS    read-only
    STATUS    mandatory
    DESCRIPTION
            "This variable identifies the group within the
            repeater for which this entry contains
            information. This value is never greater than
            rptrBasGroupCapacity."
    REFERENCE
            "Reference [12] 19.2.5.2, groupID."
    ::= { rptrBasicGroupEntry 2 }

rptrBasGroupDescr OBJECT-TYPE
    SYNTAX    DisplayString (0..255)
    ACCESS    read-only
    STATUS    mandatory
    DESCRIPTION
            "A textual description of the group. This value
            should include the full name and version
            identification of the group's hardware type and
            indicate how the group is differentiated from
            other groups in the repeater.  'Wilma Flintstone
            6-Port FOIRL Plug-in Module, Rev A' or 'Barney
            Rubble 10BASE-T 4-port SIMM socket V. 2.1' are
            examples of valid group descriptions.

            It is mandatory that this only contain printable
            ASCII characters."
    REFERENCE
            "No reference (new object)."
    ::= { rptrBasicGroupEntry 3 }

rptrBasGroupObjectID OBJECT-TYPE
    SYNTAX    OBJECT IDENTIFIER
    ACCESS    read-only
    STATUS    mandatory
    DESCRIPTION
            "The vendor's authoritative identification of the
            group.  This value is allocated within the SMI
            enterprises subtree (1.3.6.1.4.1) and provides a
            straight-forward and unambiguous means for

            determining what kind of group is being managed.

            For example, this variable could take the value
            1.3.6.1.4.1.4242.1.2.14 if vendor 'Flintstones,
            Inc.' was assigned the subtree 1.3.6.1.4.1.4242,
            and had assigned the identifier
            1.3.6.1.4.1.4242.1.2.14 to its 'Wilma Flintstone
            6-Port FOIRL Plug-in Module.'"
    REFERENCE
            "No reference (new object)."
    ::= { rptrBasicGroupEntry 4 }

rptrBasGroupUpTime OBJECT-TYPE
    SYNTAX    TimeTicks
    ACCESS    read-only
    STATUS    mandatory
    DESCRIPTION
            "An object that contains the value of sysUpTime at
            the time that the management information relating
            to this group was last reset.

            A value of zero would indicate that the group was
            present when the agent last restarted. A non-zero
            value would indicate that the group had been added
            to the repeater after the agent last restarted."
    REFERENCE
            "No reference (new object)."
    ::= { rptrBasicGroupEntry 5 }

rptrBasGroupNumOfPorts OBJECT-TYPE
    SYNTAX    INTEGER (1..1024)
    ACCESS    read-only
    STATUS    mandatory
    DESCRIPTION
            "The rptrBasGroupNumOfPorts is the number of ports
            contained within the group.  Valid range is 1-
            1024. Within each group, the ports are uniquely
            numbered in the range from 1 to
            rptrBasGroupNumOfPorts.

            Note:  In practice, this will generally be the
            number of ports on a module, card, or board, and
            the port numbers will correspond to numbers marked
            on the physical embodiment."
    REFERENCE

            "Reference [12] 19.2.5.2, numberOfPorts."
    ::= { rptrBasicGroupEntry 6 }

--
-- The Basic Port Table
--

rptrBasicPortTable OBJECT-TYPE
    SYNTAX    SEQUENCE OF RptrBasicPortEntry
    ACCESS    not-accessible
    STATUS    mandatory
    DESCRIPTION
            "Table of descriptive and status information about
            the ports."
    ::= { rptrBasicGroup 3 }

rptrBasicPortEntry OBJECT-TYPE
    SYNTAX    RptrBasicPortEntry
    ACCESS    not-accessible
    STATUS    mandatory
    DESCRIPTION
            "An entry in the table, containing information
            about a single port."
    INDEX    { rptrBasPortRptrID, rptrBasPortGroupID,
                rptrBasPortID }
    ::= { rptrBasicPortTable 1 }

RptrBasicPortEntry ::=
    SEQUENCE {
        rptrBasPortRptrID
            INTEGER,
        rptrBasPortGroupID
            INTEGER,
        rptrBasPortID
            INTEGER,
        rptrBasPortAdminState
            INTEGER,
        rptrBasPortAutoPartitionState
            INTEGER
    }

rptrBasPortRptrID OBJECT-TYPE
    SYNTAX    INTEGER (1..1024)
    ACCESS    read-only
    STATUS    mandatory

    DESCRIPTION
            "This variable identifies the repeater containing
            the port for which this entry contains
            information."
    ::= { rptrBasicPortEntry 1 }

rptrBasPortGroupID OBJECT-TYPE
    SYNTAX    INTEGER (1..1024)
    ACCESS    read-only
    STATUS    mandatory
    DESCRIPTION
            "This variable identifies the group containing the
            port for which this entry contains information."
    ::= { rptrBasicPortEntry 2 }

rptrBasPortID OBJECT-TYPE
    SYNTAX    INTEGER (1..1024)
    ACCESS    read-only
    STATUS    mandatory
    DESCRIPTION
            "This variable identifies the port within the
            group within the repeater for which this entry
            contains management information. This value can
            never be greater than rptrBasGroupNumOfPorts for
            the associated group."
    REFERENCE
            "Reference [12] 19.2.6.2, portID."
    ::= { rptrBasicPortEntry 3 }

rptrBasPortAdminState OBJECT-TYPE
    SYNTAX    INTEGER {
                disabled(1),
                enabled(2)
            }
    ACCESS    read-write
    STATUS    mandatory
    DESCRIPTION
            "Setting this variable to disabled(1) disables the
            port. A disabled port neither transmits nor
            receives.  Once disabled, a port must be
            explicitly enabled to restore operation. A port
            which is disabled when power is lost or when a
            reset is exerted shall remain disabled when normal
            operation resumes.

            The admin state takes precedence over auto-
            partition and functionally operates between the
            auto-partition mechanism and the AUI/PMA.

            Setting this variable to enabled(2) enables the
            port and exerts a BEGIN on the port's auto-
            partition state machine.

            Note:  What the above means is that when a port
            becomes disabled, its current auto-partition state
            is frozen until the port is next enabled. When the
            port becomes enabled, the auto-partition state
            becomes notAutoPartitioned, regardless of its
            pre-disabling state. This text will be clarified
            in the next draft."
    REFERENCE
            "Reference [12] 19.2.6.2, portAdminState and [12]
            19.2.6.3, portAdminControl."
    ::= { rptrBasicPortEntry 4 }

rptrBasPortAutoPartitionState OBJECT-TYPE
    SYNTAX    INTEGER {
                autoPartitioned(1),
                notAutoPartitioned(2)
            }
    ACCESS    read-only
    STATUS    mandatory
    DESCRIPTION
            "The autoPartitionState flag indicates whether the
            port is currently partitioned by the repeater's
            auto-partition protection.

            The conditions that cause port partitioning are
            specified in partition state machine in Sect. 9
            [11]. They are not differentiated here."
    REFERENCE
            "Reference [12] 19.2.6.2, autoPartitionState."
    ::= { rptrBasicPortEntry 5 }

--
-- The MONITOR GROUP
--
-- Implementation of this group is optional, but within the
-- group all elements are mandatory.  If a managed repeater
-- implements any part of this group, the entire group shall
-- be implemented.

--
-- The Repeater Monitor Table
--

rptrMonitorTable OBJECT-TYPE
    SYNTAX    SEQUENCE OF RptrMonitorEntry
    ACCESS    not-accessible
    STATUS    mandatory
    DESCRIPTION
            "Statistics for a collection of repeaters in a
            particular system."
    ::= { rptrMonitorGroup 1 }

rptrMonitorEntry OBJECT-TYPE
    SYNTAX    RptrMonitorEntry
    ACCESS    not-accessible
    STATUS    mandatory
    DESCRIPTION
            "An entry in the table, containing statistics for
            a single repeater."
    INDEX    { rptrMonID }
    ::= { rptrMonitorTable 1 }

RptrMonitorEntry ::=
    SEQUENCE {
        rptrMonID
            INTEGER,
        rptrMonTransmitCollisions
            Counter,
        rptrMonMJLPs
            Counter
    }

rptrMonID OBJECT-TYPE
    SYNTAX    INTEGER (1..1024)
    ACCESS    read-only
    STATUS    mandatory

    DESCRIPTION
            "This variable identifies the repeater for which
            this entry contains monitor information."
    ::= { rptrMonitorEntry 1 }

rptrMonTransmitCollisions OBJECT-TYPE
    SYNTAX    Counter
    ACCESS    read-only
    STATUS    mandatory
    DESCRIPTION
            "This counter is incremented every time the
            repeater state machine enters the TRANSMIT
            COLLISION state from any state other than ONE PORT
            LEFT (Ref: Fig 9-2) [11].

            Note:  The approximate minimum time for counter
            rollover is 16 hours."
    REFERENCE
            "Reference [12] 19.2.3.2, transmitCollisions."
    ::= { rptrMonitorEntry 2 }

rptrMonMJLPs OBJECT-TYPE
    SYNTAX    Counter
    ACCESS    read-only
    STATUS    mandatory
    DESCRIPTION
            "The repeater MJLPs object counts the number of
            times the repeater enters the DISABLE OUTPUT state
            in the MAU Jabber Lockup Protection state diagram
            (Fig. 9-5) [11].

            Note:  The approximate minimum time for counter
            rollover is 200 days."
    REFERENCE
            "Reference [12] 19.2.3.2, repeaterMJLPs."
    ::= { rptrMonitorEntry 3 }

--
-- The Port Monitor Table
--

rptrMonitorPortTable OBJECT-TYPE
    SYNTAX    SEQUENCE OF RptrMonitorPortEntry
    ACCESS    not-accessible
    STATUS    mandatory

    DESCRIPTION
            "Table of performance and error statistics for the
            ports."
    ::= { rptrMonitorGroup 2 }

rptrMonitorPortEntry OBJECT-TYPE
    SYNTAX    RptrMonitorPortEntry
    ACCESS    not-accessible
    STATUS    mandatory
    DESCRIPTION
            "An entry in the table, containing performance and
            error statistics for a single port."
    INDEX    { rptrMonPortRptrID, rptrMonPortGroupID,
                rptrMonPortID }
    ::= { rptrMonitorPortTable 1 }

RptrMonitorPortEntry ::=
    SEQUENCE {
        rptrMonPortRptrID
            INTEGER,
        rptrMonPortGroupID
            INTEGER,
        rptrMonPortID
            INTEGER,
        rptrMonPortReadableFrames
            Counter,
        rptrMonPortReadableOctets
            Counter,
        rptrMonPortFrameCheckSequenceErrs
            Counter,
        rptrMonPortAlignmentErrors
            Counter,
        rptrMonPortFrameTooLongs
            Counter,
        rptrMonPortShortEvents
            Counter,
        rptrMonPortRunts
            Counter,
        rptrMonPortCollisions
            Counter,
        rptrMonPortLateCollisions
            Counter,
        rptrMonPortDataRateMismatches
            Counter,
        rptrMonPortAutoPartitions

            Counter
    }

rptrMonPortRptrID OBJECT-TYPE
    SYNTAX    INTEGER (1..1024)
    ACCESS    read-only
    STATUS    mandatory
    DESCRIPTION
            "Repeater ID for identifying the port."
    ::= { rptrMonitorPortEntry 1 }

rptrMonPortGroupID OBJECT-TYPE
    SYNTAX    INTEGER (1..1024)
    ACCESS    read-only
    STATUS    mandatory
    DESCRIPTION
            "Group ID for identifying the port."
    ::= { rptrMonitorPortEntry 2 }

rptrMonPortID OBJECT-TYPE
    SYNTAX    INTEGER (1..1024)
    ACCESS    read-only
    STATUS    mandatory
    DESCRIPTION
            "Port ID for identifying the port."
    REFERENCE
            "Reference [12] 19.2.6.2, portID."
    ::= { rptrMonitorPortEntry 3 }

rptrMonPortReadableFrames OBJECT-TYPE
    SYNTAX    Counter
    ACCESS    read-only
    STATUS    mandatory
    DESCRIPTION
            "A representation of the total frames of valid
            frame length. This counter is incremented by one
            for each frame whose OctetCount is greater than or
            equal to minFrameSize and less than or equal to
            maxFrameSize (Ref: 4.4.2.1 [11]) and for which
            FCSError is not asserted.

            Note:  The approximate minimum time between
            counter rollovers is 81 hours."
    REFERENCE
            "Reference [12] 19.2.6.2, readableFrames."

    ::= { rptrMonitorPortEntry 4 }

rptrMonPortReadableOctets OBJECT-TYPE
    SYNTAX    Counter
    ACCESS    read-only
    STATUS    mandatory
    DESCRIPTION
            "Increment counter by OctetCount for each frame
            which which has been determined to be a readable
            frame.

            Note:  The approximate minimum time between
            counter rollovers is 58 minutes."
    REFERENCE
            "Reference [12] 19.2.6.2, readableOctets."
    ::= { rptrMonitorPortEntry 5 }

rptrMonPortFrameCheckSequenceErrs OBJECT-TYPE
    SYNTAX    Counter
    ACCESS    read-only
    STATUS    mandatory
    DESCRIPTION
            "Increment counter by one for each frame with
            FCSError and without FramingError and whose
            OctetCount is greater than or equal to
            minFrameSize and less than or equal to
            maxFrameSize (Ref: 4.4.2.1 [11]).

            Note:  The approximate minimum time between
            counter rollovers is 81 hours."
    REFERENCE
            "Reference [12] 19.2.6.2,
            frameCheckSequenceErrors."
    ::= { rptrMonitorPortEntry 6 }

rptrMonPortAlignmentErrors OBJECT-TYPE
    SYNTAX    Counter
    ACCESS    read-only
    STATUS    mandatory
    DESCRIPTION
            "Increment counter by one for each frame with
            FCSError and FramingError and whose octetCount is
            greater than or equal to minFrameSize and less
            than or equal to maxFrameSize (Ref: 4.4.2.1 [11]).

            Note:  The approximate minimum time between
            counter rollovers is 81 hours."
    REFERENCE
            "Reference [12] 19.2.6.2, alignmentErrors."
    ::= { rptrMonitorPortEntry 7 }

rptrMonPortFrameTooLongs OBJECT-TYPE
    SYNTAX    Counter
    ACCESS    read-only
    STATUS    mandatory
    DESCRIPTION
            "Increment counter by one for each frame whose
            OctetCount is greater than maxFrameSize (Ref:
            4.4.2.1 [11]).

            Note:  The approximate minimum time between
            counter rollovers is 61 days."
    REFERENCE
            "Reference [12] 19.2.6.2, framesTooLong."
    ::= { rptrMonitorPortEntry 8 }

rptrMonPortShortEvents OBJECT-TYPE
    SYNTAX    Counter
    ACCESS    read-only
    STATUS    mandatory
    DESCRIPTION
            "Increment counter by one for each carrier event
            whose ActivityDuration is greater than
            ShortEventMinTime and less than ShortEventMaxTime.
            ShortEventMinTime represents any event of
            sufficient duration to initiate transmission by a
            repeater. ShortEventMaxTime is greater than 7.4uS
            and less than 8.2uS. ShortEventMaxTime has
            tolerances included to provide for circuit losses
            between a conformance test point at the AUI and
            the measurement point within the state machine.

            Note: shortEvents may indicate an externally
            generated noise hit which will cause the relay to
            transmit Runts to its other ports, or propagate a
            collision (which may be late) back to the
            transmitting DTE and damaged frames to the rest of
            the network. Such shortEvents are not a feature of
            normal network activity. Also it should be noted
            that a MAU that is attached to a coax segment may

            have several carrier dropouts on the DI circuit
            before the CI circuit is active and stable. Such
            dropouts will increment the shortEvent counter but
            are considered normal for a coax segment."
    REFERENCE
            "Reference [12] 19.2.6.2, shortEvents."
    ::= { rptrMonitorPortEntry 9 }

rptrMonPortRunts OBJECT-TYPE
    SYNTAX    Counter
    ACCESS    read-only
    STATUS    mandatory
    DESCRIPTION
            "Increment counter by one for each carrier event
            whose ActivityDuration is greater than
            ShortEventMaxTime and less than  RuntMaxTime.
            RuntMaxTime is greater than 53.2uS and less than
            56.0uS.

            An event whose length is greater than 7.4uS but
            less than 8.2uS shall increment either the
            ShortEvent object or the runts object but not
            both.

            A non-collision event greater than 53.2uS but less
            than 56.0uS may or may not be counted as a runt.
            A non-collision event greater than or equal to
            56.0uS shall not be counted as a Runt.
            RuntMaxTime has tolerances included to provide for
            circuit losses between a conformance test point at
            the AUI and the measurement point within the state
            machine.

            Note:  Runts do not indicate a problem in the
            network.  The approximate minimum time for counter
            rollover is 16 hours."
    REFERENCE
            "Reference [12] 19.2.6.2, runts."
    ::= { rptrMonitorPortEntry 10 }

rptrMonPortCollisions OBJECT-TYPE
    SYNTAX    Counter
    ACCESS    read-only
    STATUS    mandatory
    DESCRIPTION

            "Increment counter by one for each carrier event
            in which the CIPresent(X) variable has the value
            SQE (see 9.6.6.2 [11]).

            Note:    The approximate minimum time for counter
            rollover is 16 hours."
    REFERENCE
            "Reference [12] 19.2.6.2, collisions."
    ::= { rptrMonitorPortEntry 11 }

rptrMonPortLateCollisions OBJECT-TYPE
    SYNTAX    Counter
    ACCESS    read-only
    STATUS    mandatory
    DESCRIPTION
            "Increment counter by one for each carrier event
            in which the CIPresent(X) variable has the value
            SQE (see 9.6.6.2 [11]) at any time when the
            ActivityDuration is greater than the RuntMaxTime.

            A late collision is counted twice, as both a
            collision and as a late collision.
            LateCollisionThreshold has tolerances included to
            provide for circuit losses between a conformance
            test point at the AUI and the measurement point
            within the state machine.

            Note:  The approximate minimum time between
            counter rollovers is 81 hours."
    REFERENCE
            "Reference [12] 19.2.6.2, lateCollisions."
    ::= { rptrMonitorPortEntry 12 }

rptrMonPortDataRateMismatches OBJECT-TYPE
    SYNTAX    Counter
    ACCESS    read-only
    STATUS    mandatory
    DESCRIPTION
            "The dataRateMismatches object counts the number
            of times that a packet has been received by this
            port with the transmission frequency (data rate)
            detectably mismatched from the local transmit
            frequency. The exact degree is implementation-
            specific and is to be defined by the implementor
            for conformance testing.

            Note: Whether or not the repeater was able to
            maintain data integrity is beyond the scope of
            this standard."
    REFERENCE
            "Reference [12] 19.2.6.2, dataRateMismatches."
    ::= { rptrMonitorPortEntry 13 }

rptrMonPortAutoPartitions OBJECT-TYPE
    SYNTAX    Counter
    ACCESS    read-only
    STATUS    mandatory
    DESCRIPTION
            "The autoPartitions object counts the number of
            times that the repeater has automatically
            partitioned this port. The conditions that cause
            port partitioning are specified in partition state
            machine in Sect. 9 [11]. They are not
            differentiated here.

            Note:  The approximate minimum time between
            counter rollovers is 20 days."
    REFERENCE
            "Reference [12] 19.2.6.2, autoPartitions."
    ::= { rptrMonitorPortEntry 14 }

--
-- The ADDRESS TRACKING GROUP
--
-- Implementation of this group is optional; it is appropriate
-- for all systems which have the necessary metering.  If a
-- managed repeater implements any part of this group, the entire
-- group shall be implemented.

--
-- The Port Address Tracking Table
--

rptrAddrTrackTable OBJECT-TYPE
    SYNTAX    SEQUENCE OF RptrAddrTrackEntry
    ACCESS    not-accessible
    STATUS    mandatory
    DESCRIPTION
            "Table of address mapping information about the
            ports."
    ::= { rptrAddrTrackGroup 1 }

rptrAddrTrackEntry OBJECT-TYPE
    SYNTAX    RptrAddrTrackEntry
    ACCESS    not-accessible
    STATUS    mandatory
    DESCRIPTION
            "An entry in the table, containing address mapping
            information about a single port."
    INDEX    { rptrAddrRptrID, rptrAddrGroupID,
            rptrAddrPortID }
    ::= { rptrAddrTrackTable 1 }

RptrAddrTrackEntry ::=
    SEQUENCE {
        rptrAddrRptrID
            INTEGER,
        rptrAddrGroupID
            INTEGER,
        rptrAddrPortID
            INTEGER,
        rptrAddrLastSourceAddress
            MacAddress,
        rptrAddrSourceAddrChanges
            Counter
    }

rptrAddrRptrID OBJECT-TYPE
    SYNTAX    INTEGER (1..1024)
    ACCESS    read-only
    STATUS    mandatory
    DESCRIPTION
            "Repeater ID for identifying the port."
    ::= { rptrAddrTrackEntry 1 }

rptrAddrGroupID OBJECT-TYPE
    SYNTAX    INTEGER (1..1024)
    ACCESS    read-only
    STATUS    mandatory
    DESCRIPTION
            "Group ID for identifying the port."
    ::= { rptrAddrTrackEntry 2 }

rptrAddrPortID OBJECT-TYPE
    SYNTAX    INTEGER (1..1024)
    ACCESS    read-only
    STATUS    mandatory
    DESCRIPTION
            "Port index for identifying the port."
    REFERENCE
            "Reference [12] 19.2.6.2, portID."
    ::= { rptrAddrTrackEntry 3 }

rptrAddrLastSourceAddress OBJECT-TYPE
    SYNTAX    MacAddress
    ACCESS    read-only
    STATUS    mandatory
    DESCRIPTION
            "The lastSourceAddress object is the source
            address of the last readable frame (i.e., counted
            by rptrMonPortReadableFrames) received by this
            port."
    REFERENCE
            "Reference [12] 19.2.6.2, lastSourceAddress."
    ::= { rptrAddrTrackEntry 4 }

rptrAddrSourceAddrChanges OBJECT-TYPE
    SYNTAX    Counter
    ACCESS    read-only
    STATUS    mandatory
    DESCRIPTION
            "The rptrAddrSourceAddressChanges object counts

            the number of the times that the
            rptrAddrLastSourceAddress for this port has
            changed.

            Note:  This may indicate whether a link is
            connected to a single DTE or another multi-user
            segment. The approximate minimum time for counter
            rollover is 81 hours."
    REFERENCE
            "Reference [12] 19.2.6.2, sourceAddressChanges."
    ::= { rptrAddrTrackEntry 5 }

-- Traps for use by Repeaters

-- Traps are defined using the conventions in RFC 1215 [10].

rptrHealth TRAP-TYPE
    ENTERPRISE  snmpDot3RptrMgt
    VARIABLES   { rptrBasHealthState }
    DESCRIPTION
            "The rptrHealth trap conveys information related
            to the operational state of the repeater. This
            trap is sent only when the health state of the
            repeater changes.

            The rptrHealth trap must contain the
            rptrBasHealthState variable. The agent may
            optionally include the rptrBasHealthText and/or
            rptrBasHealthData variables in the varBind list.
            See the rptrBasHealthState, rptrBasHealthText, and
            rptrBasHealthData objects for descriptions of the
            information that is sent.

            The agent must throttle the generation of
            consecutive rptrHealth traps so that there is at
            least a five-second gap between them."
    REFERENCE
            "Reference [12] 19.2.3.4, hubHealth notification."
    ::= 1

rptrGroupMapChange TRAP-TYPE
    ENTERPRISE  snmpDot3RptrMgt
    VARIABLES   { rptrBasGroupMap }
    DESCRIPTION
            "This trap is sent when a change occurs in the
            group structure of a repeater. This occurs only
            when a group is logically removed from or added to
            a repeater. The varBind list contains the updated
            value of the rptrBasGroupMap variable.

            The agent must throttle the generation of
            consecutive rptrGroupMapChange traps so that there
            is at least a five-second gap between them."
    REFERENCE
            "Reference [12] 19.2.3.4, groupMapChange
            notification."
    ::= 2

rptrReset TRAP-TYPE
    ENTERPRISE  snmpDot3RptrMgt
    VARIABLES   { rptrBasHealthState }
    DESCRIPTION
            "The rptrReset trap conveys information related to
            the operational state of the repeater. This trap
            is sent on completion of a repeater reset action.
            A repeater reset action is defined as an a
            transition to the START state of Fig 9-2 in
            section 9 [11], when triggered by a management
            command (e.g., an SNMP Set on the rptrBasReset
            object).

            The agent must throttle the generation of
            consecutive rptrReset traps so that there is at
            least a five-second gap between them.

            The rptrReset trap is not sent when the agent
            restarts and sends an SNMP coldStart or warmStart
            trap. However, it is recommended that a repeater
            agent send the rptrHealth variables as optional
            variables with its coldStart and warmStart trap
            PDUs.

            The rptrBasHealthState variable must be included
            in the varbind list sent with this trap.  The
            agent may optionally include the rptrBasHealthText
            and/or rptrBasHealthData variables as well."
    REFERENCE
            "Reference [12] 19.2.3.4, hubReset notification."
    ::= 3

END
